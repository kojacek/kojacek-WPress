; ----------------------------------------------------------------- ;
; by kojacek                                                        ;
; ----------------------------------------------------------------- ;
(defun C:CT ()(setvar "COLORTHEME" (abs (1- (getvar "COLORTHEME")))))
; ----------------------------------------------------------------- ;
(princ)
