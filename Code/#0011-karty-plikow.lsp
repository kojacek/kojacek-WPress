; ----------------------------------------------------------------- ;
; by kojacek 2015                                                   ;
; ----------------------------------------------------------------- ;
(defun C:FT()
  (command
    (nth
      (abs (1- (getvar "FILETABSTATE")))
      '("_.FILETABCLOSE" "_.FILETAB")
    )
  )
  (princ)
)
; ----------------------------------------------------------------- ;
